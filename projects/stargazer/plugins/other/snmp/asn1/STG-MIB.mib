STG-MIB DEFINITIONS ::= BEGIN

IMPORTS
    enterprises,
    MODULE-IDENTITY, OBJECT-TYPE,
    Integer32,
    NOTIFICATION-TYPE               FROM SNMPv2-SMI
    DisplayString                   FROM RFC1213-MIB;

stgMIB MODULE-IDENTITY
    LAST-UPDATED "201101060000Z"
    ORGANIZATION "STG"
    CONTACT-INFO    
        "Primary Contact: Maxim Mamontov
         email:     faust@stg.dp.ua"
    DESCRIPTION
        "This MIB module defines objects for Stargazer data."
    REVISION     "201101060000Z"
    DESCRIPTION "Initial revision"
    ::= { enterprises 38313 }

stg-24 OBJECT IDENTIFIER ::= { stgMIB 1 }

users OBJECT IDENTIFIER ::= { stg-24 1 }
tariffs OBJECT IDENTIFIER ::= { stg-24 2 }
admins OBJECT IDENTIFIER ::= { stg-24 3 }
services OBJECT IDENTIFIER ::= { stg-24 4 }
corporations OBJECT IDENTIFIER ::= { stg-24 5 }

totalUsers OBJECT-TYPE
    SYNTAX      Integer32
    MAX-ACCESS  read-only
    STATUS      current
    DESCRIPTION
	"Total users registered in the billing"
    DEFVAL { 0 }
    ::= { users 1 }

onlineUsers OBJECT-TYPE
    SYNTAX      Integer32
    MAX-ACCESS  read-only
    STATUS      current
    DESCRIPTION
	"The number of currently online users"
    DEFVAL { 0 }
    ::= { users 2 }

authorizedUsers OBJECT-TYPE
    SYNTAX      Integer32
    MAX-ACCESS  read-only
    STATUS      current
    DESCRIPTION
	"The number of currently authorized users"
    DEFVAL { 0 }
    ::= { users 3 }

alwaysOnlineUsers OBJECT-TYPE
    SYNTAX      Integer32
    MAX-ACCESS  read-only
    STATUS      current
    DESCRIPTION
	"The number of users with 'always online' option"
    DEFVAL { 0 }
    ::= { users 4 }

noCashUsers OBJECT-TYPE
    SYNTAX      Integer32
    MAX-ACCESS  read-only
    STATUS      current
    DESCRIPTION
	"The number of users with negative cash"
    DEFVAL { 0 }
    ::= { users 5 }

tariffUsers OBJECT-TYPE
    SYNTAX      SEQUENCE OF UsersByTariff
    MAX-ACCESS  not-accessible
    STATUS      current
    DESCRIPTION
	"The number of users by each tariff"
    DEFVAL { 0 }
    ::= { users 6 }

usersByTariff OBJECT-TYPE
    SYNTAX      UsersByTariff
    MAX-ACCESS  not-accessible
    STATUS      current
    DESCRIPTION
        "A row describing a given tariff"
    INDEX   { tariffId }
    ::= {tariffUsers 1 }

UsersByTariff ::= SEQUENCE {
    tariffId Integer32,
    tariffName DisplayString,
    userCount Integer32
}

tariffId OBJECT-TYPE
    SYNTAX      Integer32 (0..255)
    MAX-ACCESS  read-only
    STATUS      current
    DESCRIPTION
        "The id of the tariff this table describes."
    ::= { usersByTariff 1 }

tariffName OBJECT-TYPE
    SYNTAX      DisplayString
    MAX-ACCESS  read-only
    STATUS      current
    DESCRIPTION
        "The name of the tariff this table describes."
    ::= { usersByTariff 2 }

userCount OBJECT-TYPE
    SYNTAX      Integer32
    MAX-ACCESS  read-only
    STATUS      current
    DESCRIPTION
        "The count fo users of the tariff this table describes."
    ::= { usersByTariff 3 }

disabledDetailStatsUsers OBJECT-TYPE
    SYNTAX      Integer32
    MAX-ACCESS  read-only
    STATUS      current
    DESCRIPTION
	"The number of users with disabled detail stats"
    DEFVAL { 0 }
    ::= { users 7 }

disabledUsers OBJECT-TYPE
    SYNTAX      Integer32
    MAX-ACCESS  read-only
    STATUS      current
    DESCRIPTION
	"The number of disabled users"
    DEFVAL { 0 }
    ::= { users 8 }

passiveUsers OBJECT-TYPE
    SYNTAX      Integer32
    MAX-ACCESS  read-only
    STATUS      current
    DESCRIPTION
	"The number of passive users"
    DEFVAL { 0 }
    ::= { users 9 }

creditUsers OBJECT-TYPE
    SYNTAX      Integer32
    MAX-ACCESS  read-only
    STATUS      current
    DESCRIPTION
	"The number of users with positive credit"
    DEFVAL { 0 }
    ::= { users 10 }

freeMbUsers OBJECT-TYPE
    SYNTAX      Integer32
    MAX-ACCESS  read-only
    STATUS      current
    DESCRIPTION
	"The number of users with positive freeMb"
    DEFVAL { 0 }
    ::= { users 11 }

totalTariffs OBJECT-TYPE
    SYNTAX      Integer32
    MAX-ACCESS  read-only
    STATUS      current
    DESCRIPTION
	"Total tariffs registered in the billing"
    DEFVAL { 0 }
    ::= { tariffs 1 }

END
